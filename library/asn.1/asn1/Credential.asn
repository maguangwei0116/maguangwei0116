Personalize DEFINITIONS AUTOMATIC TAGS ::= BEGIN

PersonalizeRequest ::= [PRIVATE 70] SEQUENCE { --Tag ‘FF46’
    tbhPersonalize TBHPersonalize,
    hashCode [APPLICATION 1] OCTET STRING
}

TBHPersonalize ::= SEQUENCE {
        eid OCTET STRING,
        certInfos SEQUENCE OF CustomCertInfo,
        encryptedSk OCTET STRING
}

CustomCertInfo ::= SEQUENCE {
        ciPkId OCTET STRING,
        ciPk OCTET STRING,
        euiccCrt OCTET STRING,
        eumCrt OCTET STRING
}

PersonalizeResponse ::= [PRIVATE 70] SEQUENCE  { -- Tag 'FF46’
    result INTEGER {
        ok(0),
        data-format-error(1),
        check-hash-error(2),
        save-file-error(3),
        undefined-error(127)
    }
}

SetRootKeyRequest ::= [PRIVATE 32] SEQUENCE { -- Tag 'FF20'
    rootEccSk [0] OCTET STRING OPTIONAL,
    rootAesKey [1] OCTET STRING OPTIONAL
}

SetRootKeyResponse ::= [PRIVATE 32] SEQUENCE { -- Tag 'FF20'
    setKeyResult INTEGER {
        ok(0),
        undefined-error(127)
    }
}

SignRequest ::= [PRIVATE 33] SEQUENCE { -- Tag 'FF21'
    data [0] OCTET STRING
}

SignResponse ::= [PRIVATE 33] CHOICE { -- Tag 'FF21'
    signSuccessResult OCTET STRING,
    signErrorResult INTEGER {undefinedError(127)}
}

END
