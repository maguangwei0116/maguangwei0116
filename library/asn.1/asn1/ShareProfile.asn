PROFILE DEFINITIONS AUTOMATIC TAGS ::= BEGIN
    ProfileFile ::= SEQUENCE {  -- Tag '30'
        sharedProfile  SharedProfile,                               -- Tag '30'
        hashCode  [APPLICATION 1] OCTET STRING (SIZE (32))          -- Tag '41'
    }
    SharedProfile ::= SEQUENCE {
        fileInfo FileInfo,                                          -- Tag 'A0'
        rootSk OCTET STRING,                                        -- Tag '81'
        profileKey OCTET STRING,                                    -- Tag '82'
        optProfiles SEQUENCE OF OperatorProfile                     -- Tag 'A3'
    }
    -- 文件属性信息
    FileInfo ::= SEQUENCE {
        operatorNum INTEGER,                                        --Tag '80'
        version OCTET STRING                                        --Tag '81'
    }
    -- profile和profile info的信息
    OperatorProfile ::= SEQUENCE {
        profileInfo ProfileInfo1,                                   --Tag '30'
        content  OCTET STRING                                       --Tag '81'
    }
    -- profileInfo 信息
    ProfileInfo1 ::= SEQUENCE {                                     --Tag 'A0'
        apn SEQUENCE OF ApnList,                                    --Tag 'A0'
        totalNum INTEGER,                                           --Tag '81'
        sequential BOOLEAN,                                         --Tag '82'
        preferredInfo SEQUENCE OF PreferredInfo OPTIONAL            --Tag 'A1'
    }
    ApnList ::= SEQUENCE {                                          --Tag '30'
        apnName  OCTET STRING,                                      --Tag '80'
        mccMnc  OCTET STRING                                        --Tag '81'
    }
    -- 优选网络信息
    PreferredInfo ::= SEQUENCE {
        mcc OCTET STRING,
        plmn SEQUENCE OF Plmn
    }
    Plmn ::= SEQUENCE {
        rplmn  OCTET STRING OPTIONAL,
        fplmn  OCTET STRING OPTIONAL,
        hplmn  OCTET STRING OPTIONAL,
        ehplmn  OCTET STRING OPTIONAL,
        oplmn  OCTET STRING OPTIONAL
    }

    -- Profile
    BootstrapRequest ::= [PRIVATE 127] SEQUENCE { --Tag ‘FF7F’
        tbhRequest TBHRequest,
        hashCode [APPLICATION 1] OCTET STRING     -- sha256
    }
    TBHRequest ::= SEQUENCE {
        iccid OCTET STRING,             -- ICCID为卡片文件存储格式，例：98680021436587092143, 20位
        imsi OCTET STRING,              -- IMSI为卡片文件存储格式，例如 084906001111212299，18 位
        key OCTET STRING,               -- 密文，32 位，Hex 格式
        opc OCTET STRING,               -- 密文，32 位，Hex 格式
        rotation OCTET STRING OPTIONAL, -- optional，遵从 SIM 格式，默认 4000204060，
        xoring OCTET STRING OPTIONAL,   -- optional, 遵从 SIM 格式，默认
        sqnFlag OCTET STRING OPTIONAL,  -- optional,
        rplmn OCTET STRING OPTIONAL,    -- optional, 单个，SIM 卡片文件存储格式，64F010，默认 FFFFFF
        fplmn OCTET STRING OPTIONAL,    -- optional, 多个，同上
        hplmn OCTET STRING OPTIONAL,    -- optional, SIM 卡片文件存储格式，多个，例：64F0100000 64F000000，默认 FFFFFF0000
        ehplmn OCTET STRING OPTIONAL,   -- optional, 同上
        oplmn OCTET STRING OPTIONAL     -- optional, 同上
    }

    BootstrapResponse ::= [PRIVATE 127] SEQUENCE { -- Tag 'FF7F'
        result INTEGER {
            ok(0),
            already-write-success(1),
            data-format-error(2),
            check-hash-error(3),
            write-result-error(4),
            isdp-not-supported(5),
            undefined-error(127)
        }
    }
END
